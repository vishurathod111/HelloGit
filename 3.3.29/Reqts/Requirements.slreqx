# Requirements

## 3: Autonomous Flight (Functional)
The UAV shall be able to fly a preprogrammed course without pilot intervention.

## 1: Payload Data Rate (Functional)
The UAV shall support a payload data rate out of up to 8 Mb/s.

## 4: Payload Mass (Functional)
The UAV shall support a payload mass of up to 50 kg.

### 4.1: Maximum Mass (Functional)
Maximum Mass is 50 kg

### 4.2: Minimum Mass (Functional)
Minimum Mass is 0 kg

### 4.2: Minimum Mass1.1 (Functional)
Minimum Mass is 0 kg

## 2: Payload Power Demand (Functional)
The UAV shall support a payload power demand of up to 1 kW.
